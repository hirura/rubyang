module rubyang {
	namespace "http://github.com/hirura/rubyang";
	prefix rubyang;

	organization "rubyang";
	contact "http://github.com/hirura/";
	description "The module to support some basic features";

	revision 2016-07-02 {
		description "Initial revision. Just for testing.";
	}

	container rubyang {
		list component {
			key name;
			leaf name {
				type string;
			}
			leaf hook {
				type enumeration {
					//enum start;
					enum commit;
					//enum finish;
				}
			}
			leaf file-path {
				type string {
					pattern '/.+\.rb';
				}
			}
		}
	}
}
